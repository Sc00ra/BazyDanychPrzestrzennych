FME workspace zad3.fmw

Parameters:
- SourceDataset_OGCGEOPACKAGE = $(FME_MF_DIR)Data\bdline_gb.gpkg   # GeoPackage File
- SourceDataset_GEOTIFF = ""D:\baza(danych)\lab9\ras250_gb\data\HP.tif" "D:\baza(danych)\lab9\ras250_gb\data\HT.tif" "D:\baza(danych)\lab9\ras250_gb\data\HU.tif" "D:\baza(danych)\lab9\ras250_gb\data\HW.tif" "D:\baza(danych)\lab9\ras250_gb\data\HX.tif" "D:\baza(danych)\lab9\ras250_gb\data\HY.tif" "D:\baza(danych)\lab9\ras250_gb\data\HZ.tif" "D:\baza(danych)\lab9\ras250_gb\data\NA.tif" "D:\baza(danych)\lab9\ras250_gb\data\NB.tif" "D:\baza(danych)\lab9\ras250_gb\data\NC.tif" "D:\baza(danych)\lab9\ras250_gb\data\ND.tif" "D:\baza(danych)\lab9\ras250_gb\data\NF.tif" "D:\baza(danych)\lab9\ras250_gb\data\NG.tif" "D:\baza(danych)\lab9\ras250_gb\data\NH.tif" "D:\baza(danych)\lab9\ras250_gb\data\NJ.tif" "D:\baza(danych)\lab9\ras250_gb\data\NK.tif" "D:\baza(danych)\lab9\ras250_gb\data\NL.tif" "D:\baza(danych)\lab9\ras250_gb\data\NM.tif" "D:\baza(danych)\lab9\ras250_gb\data\NN.tif" "D:\baza(danych)\lab9\ras250_gb\data\NO.tif" "D:\baza(danych)\lab9\ras250_gb\data\NR.tif" "D:\baza(danych)\lab9\ras250_gb\data\NS.tif" "D:\baza(danych)\lab9\ras250_gb\data\NT.tif" "D:\baza(danych)\lab9\ras250_gb\data\NU.tif" "D:\baza(danych)\lab9\ras250_gb\data\NW.tif" "D:\baza(danych)\lab9\ras250_gb\data\NX.tif" "D:\baza(danych)\lab9\ras250_gb\data\NY.tif" "D:\baza(danych)\lab9\ras250_gb\data\NZ.tif" "D:\baza(danych)\lab9\ras250_gb\data\OV.tif" "D:\baza(danych)\lab9\ras250_gb\data\SC.tif" "D:\baza(danych)\lab9\ras250_gb\data\SD.tif" "D:\baza(danych)\lab9\ras250_gb\data\SE.tif" "D:\baza(danych)\lab9\ras250_gb\data\SH.tif" "D:\baza(danych)\lab9\ras250_gb\data\SJ.tif" "D:\baza(danych)\lab9\ras250_gb\data\SK.tif" "D:\baza(danych)\lab9\ras250_gb\data\SM.tif" "D:\baza(danych)\lab9\ras250_gb\data\SN.tif" "D:\baza(danych)\lab9\ras250_gb\data\SO.tif" "D:\baza(danych)\lab9\ras250_gb\data\SP.tif" "D:\baza(danych)\lab9\ras250_gb\data\SR.tif" "D:\baza(danych)\lab9\ras250_gb\data\SS.tif" "D:\baza(danych)\lab9\ras250_gb\data\ST.tif" "D:\baza(danych)\lab9\ras250_gb\data\SU.tif" "D:\baza(danych)\lab9\ras250_gb\data\SV.tif" "D:\baza(danych)\lab9\ras250_gb\data\SW.tif" "D:\baza(danych)\lab9\ras250_gb\data\SX.tif" "D:\baza(danych)\lab9\ras250_gb\data\SY.tif" "D:\baza(danych)\lab9\ras250_gb\data\SZ.tif" "D:\baza(danych)\lab9\ras250_gb\data\TA.tif" "D:\baza(danych)\lab9\ras250_gb\data\TF.tif" "D:\baza(danych)\lab9\ras250_gb\data\TG.tif" "D:\baza(danych)\lab9\ras250_gb\data\TL.tif" "D:\baza(danych)\lab9\ras250_gb\data\TM.tif" "D:\baza(danych)\lab9\ras250_gb\data\TQ.tif" "D:\baza(danych)\lab9\ras250_gb\data\TR.tif" "D:\baza(danych)\lab9\ras250_gb\data\TV.tif""   # Source GeoTIFF File(s) or URL(s)
- DestDataset_POSTGIS = cw9   # Connection

Readers:
- OGCGEOPACKAGE_1: OGCGEOPACKAGE from $(SourceDataset_OGCGEOPACKAGE)
- GEOTIFF_1: GEOTIFF from $(SourceDataset_GEOTIFF)

Writers:
- POSTGIS_1: POSTGIS to $(DestDataset_POSTGIS)

scotland_and_wales_region (reader OGCGEOPACKAGE_1)
    attributes: Name text(100), Area_Code text(3), Area_Description text(50), File_Name text(100), Feature_Serial_Number mediumint, Collection_Serial_Number mediumint, Global_Polygon_ID mediumint, Admin_Unit_ID mediumint, Census_Code text(9), Hectares double, Non_Inland_Area double, Area_Type_Code text(2), Area_Type_Description text(25), Non_Area_Type_Code text(3), Non_Area_Type_Description text(36), fid int,PrimaryKey
    -> TestFilter
    -> Inspector
Inspector
TestFilter
    DEFAULT_VALUE = <UNFILTERED>
    PASSED_TEST_GROUP_OUTPUT = FIRST
    TEST_LIST:
      "BOOL_OP,AND,COMPOSITE_TEST,""""""1 AND 2 AND 3"""""",TEST_CLAUSE,TEST @Value(Area_Code) = WPE
      TEST @Value(Feature_Serial_Number) != 1840
      TEST @Value(Feature_Serial_Number) != 1841",@Value(Area_Code) = WPE
    @Value(Area_Code) = WPE -> Dissolver
    @Value(Area_Code) = WPE -> SpatialFilter [Filter]
Dissolver
    ACCUM_INPUT_ATTRS = Use Attributes From One Feature
    CLEANING_TOLERANCE = Automatic
    CONNECT_Z_MODE = First Wins
    DEAGGREGATE_INPUT = Yes
    AREA -> Clipper [CLIPPER]
GEOTIFF (reader GEOTIFF_1)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> GEOTIFF (writer POSTGIS_1)
    -> Inspector_2
GEOTIFF (writer POSTGIS_1)
Inspector_2
Creator
    GEOMTYPE = Geometry Object
    NUM = 1
    CREATED -> SQLExecutor [INITIATOR]
SQLExecutor
    COMBINE_ATTRS = Result Attributes Only
    COMBINE_GEOM = Initiator Geometry Only
    DATASET = cw9
    FORMAT = POSTGIS
    OUTPUT_FEATURES_DISPLAY = Schema and Data Features
    POSTGIS_CREATE_FEATURE_TABLES_FROM_DATA = Yes
    POSTGIS_DISABLE_COLLECTION_SPLITTING = yes
    POSTGIS_NAMED_CONNECTION = cw9
    POSTGIS_QUERY_FEATURE_TYPES_FOR_MERGE_FILTERS = Yes
    POSTGIS_READ_TIME_WITH_TIMEZONE = Yes
    POSTGIS_USE_TRUE_POSTGIS_TYPES = yes
    SQL_STATEMENT = CREATE TABLE public."cw4" AS SELECT ST_Union(geom) From "public"."Export"
    RESULT -> Inspector_3
Inspector_3
